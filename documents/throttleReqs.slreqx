# throttleReqs

## controller_1: Must convert pedal signal into throttle control signal.
The controller must convert the pedal signal into a throttle control signal.

## throttleReqs: References to throttleReqs.doc
Read-only references to Microsoft Word document.

### Input Scaling

#### inp_scl_1: Scaled data must be responsive t...
Scaled data must be responsive to full range of input data.

#### inp_scl_2: Output range for each signal must be normalized.

### PI Controller

#### pi_ctrl_1: Must implement standard proporti...
Must implement standard proportional plus integral control algorithm.

#### pi_ctrl_2: Proportional and integral gains ...
Proportional and integral gains should be adjustable.

#### pi_ctrl_3: Measures must be taken to preven...
Measures must be taken to prevent windup in integral state.

### PWM Conversion

#### pwm_1: Duty cycle must be proportional ...
Duty cycle must be proportional to controller output, when in a valid range.

#### pwm_2: PWM torque should act in positiv...
PWM torque should act in positive sense when controller output is positive or zero.

#### pwm_3: PWM torque should act in negativ...
PWM torque should act in negative sense when controller output is negative.

#### pwm_4: Duty cycle must be in range from 0 to 1.

### Output Scaling

#### out_scl_1: Scaled data must be responsive t...
Scaled data must be responsive to full range of input data.

#### out_scl_2: Output data must be scaled for d...
Output data must be scaled for direct input to driver software.

## #18: Justifications

### #19: Non-functional requirement

### #20: Non-functional requirement

### #21: Non-functional requirement

### #22: Non-functional requirement

### #23: Non-functional requirement
